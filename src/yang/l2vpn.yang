module l2vpn {

  yang-version 1.1;
  namespace "https://www.turktelekom.com.tr/l2vpn";
  prefix l2vpn;

  import ietf-inet-types {
    prefix inet;
  }
  import tailf-common {
    prefix tailf;
  }
  import tailf-ncs {
    prefix ncs;
  }
  import inventory {
    prefix inv;
  }

  description
    "L2VPN provision package.";

  revision 2023-11-20 {
    description
      "Initial revision.";
  }

  typedef l2vpn-string {
    type string {
      pattern
        '[^\s]+' {
        error-message
          "No space/s allowed.";
      }
    }
  }

  typedef pw-id-type {
    type uint32;
  }

  typedef service-id-type {
    type uint32;
  }

  typedef mtu-type {
    type uint16 {
      range "64..65535";
    }
  }

  typedef sdp-id-type {
    type uint32;
  }

  typedef state-type {
    type enumeration {
      enum enable;
      enum disable;
    }
  }

  typedef uni-type {
    type enumeration {
      enum port;
      enum serv-inst;
    }
  }

  typedef subif-id-type {
    type uint16 {
      range "2..4094";
    }
  }

  typedef encapsulation-type {
    type enumeration {
      enum dot1q-2tags;
      enum dot1q;
      enum dot1ad;
      enum e-default;
      enum untagged;
    }
  }

  typedef vlan-id-type {
    type uint16 {
      range "2..4094";
    }
    description
      "The VLAN-ID that uniquely identifies a VLAN.  This is the 12-bit
       VLAN-ID used in the VLAN Tag header.";
    reference
      "[802.1Q]";
  }

  typedef elan-index-type {
    type uint8 {
      range "1..24";
    }
  }

  grouping elan-grouping {
    leaf pw-id {
      tailf:info "Pseudowire Id";
      config false;
      tailf:cdb-oper {
        tailf:persistent true;
      }
      type pw-id-type;
    }

    leaf service-id {
      tailf:info "Service Id";
      config false;
      tailf:cdb-oper {
        tailf:persistent true;
      }
      type service-id-type;
    }

    leaf service-description {
      tailf:info "Description for the service";
      type l2vpn-string;
    }

    leaf mtu {
      tailf:info "Interface/service MTU";
      type mtu-type;
      default 1514;
    }

    leaf split-horizon {
      tailf:info "When enable, split horizon will be added for AC in same bridge-domain";
      type state-type;
      default enable;
    }

    list endpoint {
      tailf:info "Device that is attached to CE.";

      key "device";

      leaf device {
        tailf:info "PE Device";
        type leafref {
          path "/ncs:devices/ncs:device/ncs:name";
        }
      }

      list remote-peer {
        tailf:info "Remote peer information";
        config false;
        tailf:cdb-oper {
          tailf:persistent true;
        }

        key name;

        leaf name {
          tailf:info "Remote peer name";
          type string;
        }

        leaf sdp-id {
          tailf:info "Service sdp id assigned by resource-manager";
          type sdp-id-type;
        }

        leaf address {
          tailf:info "MPLS system ip address.";
          type inet:ipv4-address;
        }
      }

      list pe-interface {
        tailf:info "PE Device Interface";

        key "id-int";

        leaf id-int {
          tailf:info "Just a number used as index";
          type elan-index-type;
        }

        leaf subif-id {
          tailf:info "Sub-Interface Id";
          config false;
          tailf:cdb-oper {
            tailf:persistent true;
          }
          type subif-id-type;
        }

        leaf if-size {
          tailf:info "Interface Size.Ex GigabitEthernet | TenGigabitEthernet | FortyGigE | HundredGigE | Port-channel";
          type leafref {
            path "/inv:inventory-manager/inv:device[inv:name=current()/../../device]/inv:interface/inv:if-size";
          }
        }

        leaf if-number {
          when "../if-size";
          tailf:info "Interface Size.Ex GigabitEthernet | TenGigabitEthernet | FortyGigE | HundredGigE | Port-channel";
          type leafref {
            path "/inv:inventory-manager/inv:device[inv:name=current()/../../device]/inv:interface[inv:if-size=current()/../if-size]/inv:if-number";
          }
        }

        leaf interface-description {
          tailf:info "Interface Description";
          type l2vpn-string;
        }

        leaf end-type {
          type uni-type;
          default serv-inst;
        }

        leaf encapsulation {
          when "../end-type = 'serv-inst'";
          tailf:info "Interface Encapsulation Type";
          type encapsulation-type;
          default "dot1q";
        }

        leaf s-vlan-id {
          when "../encapsulation = 'dot1ad' or ../encapsulation = 'dot1q-2tags'";
          tailf:info "Interface Encapsulation S-Vlan Id";
          type vlan-id-type;
        }

        leaf-list c-vlan-id {
          when "../encapsulation = 'dot1q-2tags' or ../encapsulation = 'dot1ad' or ../encapsulation = 'dot1q'";
          tailf:info "Interface Encapsulation C-Vlan Id";
          type vlan-id-type;
        }
      }
    }
  }

  container l2vpn {
    tailf:info "L2VPN Service Definitions";

    list elan {
      tailf:info "Ethernet LAN (E-LAN). Provides a Multipoint-to-Multipoint EVC.";

      uses ncs:service-data;
      ncs:servicepoint elan-servicepoint;

      key name;

      leaf name {
        tailf:info "ELAN Service Name";
        type l2vpn-string;
      }

      uses l2vpn:elan-grouping;
    }
  }
}
